FME workspace AGOLUPSERTDemo.fmw

Parameters:
- SourceDataset_CSV2 = $(FME_MF_DIR)Data\Original.csv   # Source CSV (Comma Separated Value) File(s)
- SourceDataset_CSV2_5 = $(FME_MF_DIR)Data\Updates.csv   # Source CSV (Comma Separated Value) File(s)

Readers:
- CSV2_2: CSV2 from $(SourceDataset_CSV2)
- ARCGISONLINEFEATURES_2: ARCGISONLINEFEATURES
- CSV2_3: CSV2 from $(SourceDataset_CSV2_5)
- ARCGISONLINEFEATURES_5: ARCGISONLINEFEATURES

Writers:
- ARCGISONLINEFEATURES_3: ARCGISONLINEFEATURES to <Unused>
- ARCGISONLINEFEATURES_4: ARCGISONLINEFEATURES

Bookmark: Part 1: Create Seed Data
Original (reader CSV2_2)
    attributes: featureid uint32, Code varchar(14), longitude x_coordinate, latitude y_coordinate, StationID uint32, Power real64, Quality real32, num_measures uint32, recorded_tstamp varchar(17)
    -> CellSignals (writer ARCGISONLINEFEATURES_3)
CellSignals (writer ARCGISONLINEFEATURES_3)
    attributes: featureid Integer, Code String(14), longitude Double, latitude Double, StationID Integer, Power Double, Quality Single, num_measures Integer, recorded_tstamp String(17)

Bookmark: Part 2: UPSERT to AGOL
CellSignals (reader ARCGISONLINEFEATURES_5)
    attributes: featureid Integer, Code String(14), longitude Double, latitude Double, StationID Integer, Power Double, Quality Single, num_measures Integer, recorded_tstamp String(17), OBJECTID OID
    -> ChangeDetector [ORIGINAL]
Updates (reader CSV2_3)
    attributes: featureid uint32, code varchar(14), longitude x_coordinate, latitude y_coordinate, stationid uint32, power real64, quality real32, num_measures uint32, recorded_tstamp varchar(17)
    -> ChangeDetector [REVISED]
ChangeDetector
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCHATTRS = code Code featureid num_measures OBJECTID power Power quality Quality recorded_tstamp stationid StationID
    MATCH_STRATEGY = Match Selected Attributes
    PREEMPTIVE_ATTRS = featureid
    UNCHANGED_OUTPUT = Output Original
    UPSERT_MODE = Yes
    UPDATED -> CellSignals (writer ARCGISONLINEFEATURES_4)
    DELETED -> CellSignals (writer ARCGISONLINEFEATURES_4)
CellSignals (writer ARCGISONLINEFEATURES_4)
    attributes: featureid Integer, Code String(14), longitude Double, latitude Double, StationID Integer, Power Double, Quality Single, num_measures Integer, recorded_tstamp String(17), OBJECTID OID
